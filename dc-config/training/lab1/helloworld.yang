module helloworld {

    yang-version 1.1;

    prefix "helloworld";

    list helloworld {
        presence "Top-level container for the helloworld app";
        description "Top level enclosing container for helloworld app
                     config and operational state data";

        leaf name {
            description "Who am I saying hello to Today?";
            type string {
                length 0..255;
                pattern '[A-Za-z0-9]*';
            }
        }

        leaf counter {
            description "Number of events";
            config false;
        }


        leaf response {
            config false;
            description "Response to input";
            type strung;
        }
    }
}
